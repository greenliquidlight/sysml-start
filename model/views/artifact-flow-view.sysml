// SysML2 Artifact Flow View Definition
// File: model/views/artifact-flow-view.sysml
//
// This file defines the artifact flow diagram view for the SysML2 modeling
// workflow. It shows how artifacts (model files, generated diagrams, docs)
// flow through the workflow pipeline.
//
// NOTE: The exact SysML2 view/expose syntax depends on your tooling version.
// The definition below uses approximate syntax. Adjust as needed for your
// SysML2 tool.
//
// The rendered output is generated by scripts/render-diagrams and stored at:
//   generated/diagrams/artifact-flow.svg

package ArtifactFlowView {

    public import WorkflowContext::*;
    public import WorkflowBehavior::*;

    // -------------------------------------------------------------------------
    // View definition
    // -------------------------------------------------------------------------

    view def WorkflowArtifactFlowView {
        doc /* Artifact flow diagram showing how .sysml model files are
               transformed into generated SVG diagrams and assembled into
               HTML documentation through the workflow pipeline.

               Intended rendering:
               - Swim-lane or linear flow diagram
               - Lanes or nodes for: Edit, Validate, Render, Build Docs, Review
               - Artifact nodes: .sysml files, SVG diagrams, HTML docs
               - Directed flow edges showing data flow between steps
               - Title: "SysML2 Workflow — Artifact Flow Diagram" */

        // TODO: Replace the comment below with the correct expose/filter
        // syntax for your SysML2 tooling once integrated.

        // expose WorkflowBehavior::textFirstWorkflow {
        //     include edit;
        //     include validate;
        //     include render;
        //     include build;
        //     include review;
        //     include flow edit.out -> validate;
        //     include flow validate.out -> render;
        //     include flow render.out -> build;
        //     include flow build.out -> review;
        // }
    }

    // -------------------------------------------------------------------------
    // Rendering instructions (for placeholder SVG generator)
    // -------------------------------------------------------------------------

    // The following metadata is used by scripts/render-diagrams to generate
    // a placeholder SVG until a real SysML2 rendering tool is integrated.
    //
    // @render-title  : SysML2 Workflow — Artifact Flow Diagram
    // @render-output : generated/diagrams/artifact-flow.svg
    // @render-nodes  : Edit Model, Validate Model, Render Diagrams,
    //                  Build Docs, Review Output
    // @render-artifacts : .sysml files, generated/diagrams/*.svg, docs/*.md,
    //                     generated/docs/index.html
    // @render-edges  : Edit→Validate, Validate→Render, Render→BuildDocs,
    //                  BuildDocs→Review

}
