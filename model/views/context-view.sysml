// SysML2 Context View Definition
// File: model/views/context-view.sysml
//
// This file defines the context diagram view for the SysML2 modeling workflow.
// It specifies which model elements are included in the context diagram and
// what relationships are rendered.
//
// NOTE: The exact SysML2 view/expose syntax depends on your tooling version.
// The definition below uses approximate syntax. Adjust as needed for your
// SysML2 tool.
//
// The rendered output is generated by scripts/render-diagrams and stored at:
//   generated/diagrams/context.svg

package ContextView {

    public import WorkflowContext::*;

    // -------------------------------------------------------------------------
    // View definition
    // -------------------------------------------------------------------------

    view def WorkflowContextView {
        doc /* Context diagram showing the key actors, systems, and top-level
               relationships in the text-first SysML2 modeling workflow.

               Intended rendering:
               - Boxes for: ModelAuthor, Reviewer, VSEnvironment, ModelRepository,
                 ValidationTool, ViewRenderer, DocumentationBuilder, CISystem
               - Directed edges showing usage and data-flow relationships
               - Title: "SysML2 Workflow — Context Diagram" */

        // TODO: Replace the comment below with the correct expose/filter
        // syntax for your SysML2 tooling once integrated.

        // expose WorkflowContext::workflowContext {
        //     include author;
        //     include reviewer;
        //     include vsCode;
        //     include repo;
        //     include validator;
        //     include renderer;
        //     include docBuilder;
        //     include ci;
        //     include authorUsesVSCode;
        //     include vsCodeEditsRepo;
        //     include validatorReadsRepo;
        //     include rendererReadsRepo;
        //     include rendererWritesDiagrams;
        //     include docBuilderReadsRepo;
        //     include ciRunsValidator;
        //     include ciRunsRenderer;
        //     include ciRunsDocBuilder;
        //     include reviewerConsumesRepo;
        // }
    }

    // -------------------------------------------------------------------------
    // Rendering instructions (for placeholder SVG generator)
    // -------------------------------------------------------------------------

    // The following metadata is used by scripts/render-diagrams to generate
    // a placeholder SVG until a real SysML2 rendering tool is integrated.
    //
    // @render-title  : SysML2 Workflow — Context Diagram
    // @render-output : generated/diagrams/context.svg
    // @render-nodes  : ModelAuthor, Reviewer, VSEnvironment, ModelRepository,
    //                  ValidationTool, ViewRenderer, DocumentationBuilder, CISystem
    // @render-edges  : author→vsCode, vsCode→repo, validator→repo,
    //                  renderer→repo, docBuilder→repo, ci→validator,
    //                  ci→renderer, ci→docBuilder, reviewer→repo

}
